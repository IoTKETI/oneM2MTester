--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Balasko, Jeno
--   Forstner, Matyas
--   Koppany, Csaba
--
--/////////////////////////////////////////////////////////////////////////////
X682
DEFINITIONS

AUTOMATIC TAGS
EXTENSIBILITY IMPLIED

::=

BEGIN

IMPORTS ;

ERROR-CLASS ::= CLASS
{
  &category	PrintableString(SIZE(1)),
  &code		INTEGER,
  &Type	DEFAULT INTEGER
}
WITH SYNTAX {&category &code [&Type]}

ErrorSet ERROR-CLASS ::=
{
  {"A" 1 [1] INTEGER} |
  {"A" 2 [1] VisibleString} |
  {"B" 1 [1] PrintableString} |
  {"B" 2 [1] BOOLEAN} |
  oneErrorObject
}

oneErrorObject ERROR-CLASS ::= { "C" 3 ENUMERATED{foobar} }

ErrorReturn ::= SEQUENCE
{
  errorCategory	ERROR-CLASS.&category ({ErrorSet}) OPTIONAL,
  errors	SEQUENCE OF SEQUENCE
  {
    errorCode	ERROR-CLASS.&code({ErrorSet}{@errorCategory}),
    errorInfo	[99] ERROR-CLASS.&Type({ErrorSet}{@errorCategory,@.errorCode})
  } OPTIONAL
}

errorReturn1 ErrorReturn ::=
{
  errorCategory "A",
  errors
  {
    {
      errorCode 1,
      errorInfo errorSet-1-Type : 20020716
    },
    {
      errorCode 2,
      errorInfo errorSet-2-Type : "If U can decode this, U can be happy. Smile! :-)"
    }
  }
}

  ber-errorReturn1 OCTET STRING ::= '304D800141A148300C020101BF6306810401317DEC3038020102BF63328130496620552063616E206465636F646520746869732C20552063616E2062652068617070792E20536D696C6521203A2D29'H

errorReturn2 ErrorReturn ::=
{
  errorCategory "3",
  errors
  {
    {
      errorCode 3,
      errorInfo oneErrorObject-Type : foobar
    }
  }
}

END
