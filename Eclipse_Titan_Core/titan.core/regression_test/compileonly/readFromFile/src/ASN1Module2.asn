--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Szabo, Bence Janos
--
--/////////////////////////////////////////////////////////////////////////////
ASN1Module2
DEFINITIONS

AUTOMATIC TAGS

::=

BEGIN

IMPORTS ; -- nothing

asn1module2 INTEGER ::= 2

END
