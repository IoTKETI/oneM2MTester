--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Balasko, Jeno
--   Baranyi, Botond
--
--/////////////////////////////////////////////////////////////////////////////

ImportedLowerAsn 

DEFINITIONS AUTOMATIC TAGS ::=

BEGIN
-- EXPORTS <exports clause>;
IMPORTS 
IIC-Request FROM ImportedAsn 
;

-- MODULE-BODY
MYREAL-LOWER ::= REAL
MyLowerType ::= IIC-Request
END
