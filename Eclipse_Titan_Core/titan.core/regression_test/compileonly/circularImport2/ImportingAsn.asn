--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Balasko, Jeno
--   Baranyi, Botond
--
--/////////////////////////////////////////////////////////////////////////////

ImportingAsn DEFINITIONS AUTOMATIC TAGS ::=

BEGIN
-- EXPORTS <exports clause>;
IMPORTS

IICrequestTX, IICresponseTX FROM ImportedAsn { iso (1) standard (0) calm-management (24102) iitsscu (4) asnm-1 (1) }
;
-- MODULE-BODY

MYREALTYPE ::= REAL
-- MX-SAP generic OBJECT CLASS

MXSERV ::= CLASS {
      &mxref INTEGER(0..255),
      &MXParam
	}
	
MFSAP-CR::=MXSERV

iICrequestTX	MFSAP-CR::={&mxref 11, &MXParam IICrequestTX} 
iICresponseTX	MFSAP-CR::={&mxref 12, &MXParam IICresponseTX}

END
