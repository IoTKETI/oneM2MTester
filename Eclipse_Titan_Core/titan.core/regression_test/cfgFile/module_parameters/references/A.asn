A DEFINITIONS

-- [(AUTOMATIC|EXPLICIT|IMPLICIT) TAGS]
-- the default is EXPLICIT TAGS
  AUTOMATIC TAGS ::=

BEGIN
-- EXPORTS <exports clause>;
IMPORTS;
-- MODULE-BODY

-- BOOLEAN
ASN1MyBooleanType ::= BOOLEAN
myBooleanasn1Value1 ASN1MyBooleanType ::= FALSE
myBooleanasn1Value2 BOOLEAN ::= TRUE

-- BIT STRING
MyBitstringType ::= BIT STRING
myBitstringValue1 MyBitstringType ::=  '0101010101010101'B
myBitstringValue2 BIT STRING ::= '1010101010101010'B
-- OCTET STRING
MyOctetStringType ::= OCTET STRING
myOctetstringValue1 MyOctetStringType ::= 'ABCDEF0123456789'H
myOctetstringValue2  OCTET STRING ::= '1234567890ABCDEF'H

MyPrintableString ::= PrintableString

MyIntegerType1 ::= INTEGER
myInteger MyIntegerType1 ::= 13
MyRealType1 ::= REAL
myReal MyRealType1 ::= 3.1415


END
