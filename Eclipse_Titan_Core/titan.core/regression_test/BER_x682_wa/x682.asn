--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Balasko, Jeno
--   Forstner, Matyas
--   Szabados, Kristof
--
--/////////////////////////////////////////////////////////////////////////////
X682
DEFINITIONS

AUTOMATIC TAGS
EXTENSIBILITY IMPLIED

::=
BEGIN

/*
ERROR-CLASS ::= CLASS
{
  &category	PrintableString(SIZE(1)),
  &code		INTEGER,
  &Type
}
WITH SYNTAX {&category &code &Type}

ErrorSet ERROR-CLASS ::=
{
  {"A" 1 INTEGER} |
  {"A" 2 VisibleString} |
  {"B" 1 PrintableString} |
  {"B" 2 BOOLEAN}
}

ErrorReturn ::= SEQUENCE
{
  errorCategory	ERROR-CLASS.&category ({ErrorSet}) OPTIONAL,
  errors	SEQUENCE OF SEQUENCE
  {
    errorCode	ERROR-CLASS.&code({ErrorSet}{@errorCategory}),
    errorInfo	ERROR-CLASS.&Type({ErrorSet}{@errorCategory,@.errorCode})
  } OPTIONAL
}

*/

ErrorReturn ::= SEQUENCE
{
  errorCategory	PrintableString(SIZE(1)) OPTIONAL,
  errors	SEQUENCE OF SEQUENCE
  {
    errorCode	INTEGER,
    errorInfo	[99] CHOICE
    {
      iNTEGER [1] INTEGER,
      visibleString [1] VisibleString,
      printableString [1] PrintableString,
      bOOLEAN [1] BOOLEAN
    }
    /*#asn1_compiler#
      OPENTYPE
      @errorCategory	@.errorCode	;
      	"A"	1	iNTEGER		;
      	"A"	2	visibleString	;
      	"B"	1	printableString	;
      	"B"	2	bOOLEAN		;
    #asn1_compiler#*/
  } OPTIONAL
}

errorReturn1 ErrorReturn ::=
{
  errorCategory "A",
  errors
  {
    {
      errorCode 1,
      errorInfo iNTEGER : 20020716
    },
    {
      errorCode 2,
      errorInfo visibleString : "If U can decode this, U can be happy. Smile! :-)"
    }
  }
}

  ber-errorReturn1 OCTET STRING ::= '304D800141A148300C020101BF6306810401317DEC3038020102BF63328130496620552063616E206465636F646520746869732C20552063616E2062652068617070792E20536D696C6521203A2D29'H

END
