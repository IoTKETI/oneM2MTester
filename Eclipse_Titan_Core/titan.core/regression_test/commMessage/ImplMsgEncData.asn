--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Balasko, Jeno
--   Delic, Adam
--   Raduly, Csaba
--   Szabados, Kristof
--
--/////////////////////////////////////////////////////////////////////////////
ImplMsgEncData
DEFINITIONS
AUTOMATIC TAGS
::=
BEGIN

IMPORTS ; -- nothing

PDU1 ::= GeneralString
PDU2 ::= SEQUENCE {
  f1 INTEGER,
  f2 OCTET STRING,
  f3 BOOLEAN
}
END
