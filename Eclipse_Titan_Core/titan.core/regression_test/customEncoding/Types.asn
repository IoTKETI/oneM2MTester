--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Baranyi, Botond
--
--/////////////////////////////////////////////////////////////////////////////

Types
DEFINITIONS

AUTOMATIC TAGS ::=

BEGIN
IMPORTS;

Seq ::= SEQUENCE {
  num INTEGER,
  str VisibleString
}

Set2 ::= SET {
  num INTEGER,
  str VisibleString
}

SeqOf ::= SEQUENCE OF INTEGER

SetOf ::= SEQUENCE OF INTEGER

Choice ::= CHOICE {
  num INTEGER,
  str VisibleString
}

END
