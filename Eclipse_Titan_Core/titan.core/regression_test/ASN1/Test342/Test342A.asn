--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Balasko, Jeno
--   Kulcsar, Endre
--   Szabados, Kristof
--
--/////////////////////////////////////////////////////////////////////////////
Test342A
DEFINITIONS

AUTOMATIC TAGS

::=

BEGIN

MyRealType1 ::= REAL

myRealValue1 MyRealType1 ::= 3.2 -- {mantissa 314159,base 10, exponent -10}

END
