--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Balasko, Jeno
--   Kulcsar, Endre
--   Szabados, Kristof
--
--/////////////////////////////////////////////////////////////////////////////
Test44
DEFINITIONS

IMPLICIT TAGS

::=

BEGIN

redefinedValue OCTET STRING ::= '0123456789ABCDEF'H

redefinedValue OCTET STRING ::= 'ABCDEF0123456789'H

END
