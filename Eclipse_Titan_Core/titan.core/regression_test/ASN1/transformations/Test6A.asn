--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Balasko, Jeno
--   Koppany, Csaba
--   Kulcsar, Endre
--   Raduly, Csaba
--   Szabados, Kristof
--
--/////////////////////////////////////////////////////////////////////////////
Test6A --  A
DEFINITIONS

AUTOMATIC TAGS


::=

BEGIN

IMPORTS ; -- nothing

MySequenceType1 ::= SEQUENCE
		{
		field1 INTEGER OPTIONAL,
		field2 BOOLEAN OPTIONAL
		}

MySetType1 ::= SET
		{
		field1 INTEGER OPTIONAL,
		field2 BOOLEAN OPTIONAL
		}

MyChoiceType ::= CHOICE
		{
		field1 INTEGER,
		field2 BOOLEAN
		}


END
