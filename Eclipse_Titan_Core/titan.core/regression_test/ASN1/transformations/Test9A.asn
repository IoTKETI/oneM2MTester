--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Balasko, Jeno
--   Koppany, Csaba
--   Kulcsar, Endre
--   Raduly, Csaba
--   Szabados, Kristof
--
--/////////////////////////////////////////////////////////////////////////////
Test9A --  A
DEFINITIONS

AUTOMATIC TAGS


::=

BEGIN

IMPORTS ; -- nothing

MySequenceType1 ::= SEQUENCE
		{
		field1 INTEGER,
		field2 BOOLEAN
		}

MySequenceType2 ::= SEQUENCE
		{
		field1 INTEGER,
		field2 BOOLEAN,
		field3 BIT STRING,
		field4 OCTET STRING
		}



MySetType1 ::= SET
		{
		field1 INTEGER,
		field2 BOOLEAN
		}

MySetType2 ::= SET
		{
		field1 INTEGER,
		field2 BOOLEAN,
		field3 BIT STRING,
		field4 OCTET STRING
		}
END
