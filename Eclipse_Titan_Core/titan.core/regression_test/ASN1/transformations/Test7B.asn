--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Balasko, Jeno
--   Koppany, Csaba
--   Kulcsar, Endre
--   Raduly, Csaba
--   Szabados, Kristof
--
--/////////////////////////////////////////////////////////////////////////////
Test7B --  B
DEFINITIONS

IMPLICIT TAGS


::=

BEGIN

IMPORTS ; -- nothing

MySequenceType1 ::= SEQUENCE
		{
		field1 [3] INTEGER OPTIONAL,
		field2 BOOLEAN OPTIONAL
		}

MySetType1 ::= SET
		{
		field1 [1] INTEGER OPTIONAL,
		field2 [0] BOOLEAN OPTIONAL
		}

MyChoiceType ::= CHOICE
		{
		field1 [5] INTEGER,
		field2 [6] BOOLEAN
		}


END
