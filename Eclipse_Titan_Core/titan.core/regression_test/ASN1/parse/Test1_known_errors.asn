--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Balasko, Jeno
--   Hanko, Matyas
--   Koppany, Csaba
--   Szabados, Kristof
--
--/////////////////////////////////////////////////////////////////////////////
Test1-known-errors

DEFINITIONS

AUTOMATIC TAGS

::=

BEGIN
-- 19 ENUMERATED *******************************************************
MyEnumeratedType1 ::= ENUMERATED {a,b,...!,c}

--29 SELECTION TYPES *******************************************************************

--MySelectionType ::= field1 < MyChoiceType1

-- MySelectionValue MySelectionType ::= 123

--33 EMBEDDED PDV *******************************************************************
-- COMMENT ENTIRE SECTION

MyEmbeddedPDVType1 ::= EMBEDDED PDV

myEmbeddedPDVValue1 MyEmbeddedPDVType1 ::=
{

identification syntaxes :
			{
			 abstract {qw(0) er(0) ty(3)},
			 transfer myObjectIdentifierValue1
			},
data-value '1234567890ABCDEF'H

}

myEmbeddedPDVValue2 MyEmbeddedPDVType1 ::=
{

identification syntax : myObjectIdentifierValue2,

data-value '1234567890ABCDEF'H

}

myEmbeddedPDVValue3 MyEmbeddedPDVType1 ::=
{

identification presentation-context-id : myIntegerValue1,

data-value '1234567890ABCDEF'H

}

myEmbeddedPDVValue4 MyEmbeddedPDVType1 ::=
{

identification context-negotiation : {
				presentation-context-id   333,
				transfer-syntax { asdf(9) dfghj(6) }
				   },

data-value '1234567890ABCDEF'H

}

myEmbeddedPDVValue5 MyEmbeddedPDVType1 ::=
{

identification transfer-syntax : {0 0 0 0 0 0},

data-value '1234567890ABCDEF'H

}

myEmbeddedPDVValue6 MyEmbeddedPDVType1 ::=
{

identification fixed : NULL

data-value '1234567890ABCDEF'H

}

--34 EXTERNAL *******************************************************************
-- COMMENT ENTIRE SECTION
MyExternalType1 ::= EXTERNAL

myExternalValue1 MyExternalType1::=

{
identification syntax : {0 1 2 3 4 5},

data-value-descriptor myObjectDescriptorValue1,

data-value '1234567890ABCDEF'H

}

myExternalValue2 MyExternalType1 ::=

{
identification presentation-context-id : 5,

data-value-descriptor myObjectDescriptorValue1,

data-value '1234567890ABCDEF'H

}

myExternalValue3 MyExternalType1 ::=

{
identification context-negotiation {
				presentation-context-id   333,
				transfer-syntax { asdf(9) dfghj(6) }
				   },

data-value-descriptor myObjectDescriptorValue1,

data-value '1234567890ABCDEF'H

}

END
