--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Balasko, Jeno
--   Kulcsar, Endre
--   Raduly, Csaba
--
--/////////////////////////////////////////////////////////////////////////////
Test66

DEFINITIONS

AUTOMATIC TAGS

::=

BEGIN

IMPORTS ; -- nothing

MyEnumeratedType1 ::= ENUMERATED {a(0),b(1),..., c(2)}

myEnumearetedValue1 MyEnumeratedType1 ::= a

myEnumearetedValue2 MyEnumeratedType1 ::= b

myEnumearetedValue3 MyEnumeratedType1 ::= c

END
