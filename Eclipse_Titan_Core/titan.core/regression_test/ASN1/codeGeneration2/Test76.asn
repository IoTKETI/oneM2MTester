--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Balasko, Jeno
--   Koppany, Csaba
--   Kulcsar, Endre
--   Raduly, Csaba
--   Szabados, Kristof
--
--/////////////////////////////////////////////////////////////////////////////
Test76

DEFINITIONS

AUTOMATIC TAGS

::=

BEGIN

IMPORTS ; -- nothing

MySequenceType1 ::= SEQUENCE {
  			     field1 INTEGER,
			     field2 BOOLEAN,
			     field3 NULL,
			     field4 OCTET STRING,
			     field5 BIT STRING,
			     field6 ENUMERATED {a,b,c},
			     field7 REAL
			    }

MyChoiceType1 ::= CHOICE
			    {
  			     field1 INTEGER,
			     field2 BOOLEAN,
			     field3 NULL,
			     field4 OCTET STRING,
			     field5 BIT STRING,
			     field6 ENUMERATED {a,b,c},
			     field7 REAL,
			     field8 MySequenceType1
			    }

MySetType1 ::= SET {
  			     field1 INTEGER,
			     field2 BOOLEAN,
			     field3 NULL,
			     field4 OCTET STRING,
			     field5 BIT STRING,
			     field6 ENUMERATED {a,b,c},
			     field7 REAL,
			     field8 MySequenceType1
			    }

MySetOfType1 ::= SET OF INTEGER

MySetOfType2 ::= SET OF MySequenceType1

MySetOfType3 ::= SET OF MyChoiceType1

MySetOfType4 ::= SET OF MySetType1


mySetOfValue1 MySetOfType1 ::= {1,0,-1,1000, -1000}

mySetOfValue2 MySetOfType2 ::=
{
   {
  			     field1 444,
			     field2 TRUE,
			     field3 NULL,
			     field4 'FFFF'H,
			     field5 '00'B,
			     field6  a,
			     field7 5.2 -- {mantissa 314159,base 10, exponent -10}

   },
   {
  			     field1 123,
			     field2 FALSE,
			     field3 NULL,
			     field4 'ABCD'H,
			     field5 '010101010'B,
			     field6  b,
			     field7 5.2 -- {mantissa 9,base 10, exponent 1}

   },
   {
  			     field1 340,
			     field2 FALSE,
			     field3 NULL,
			     field4 '1234'H,
			     field5 '110000'B,
			     field6  c,
			     field7 5.2 -- {mantissa 4,base 10, exponent -1}

   }



}


mySetOfValue3 MySetOfType3 ::=
{

    field1 : 762,
    field5 : '01010'B,
    field2 : TRUE,
    field4 : 'FFFF'H,
    field7 : 5.2, -- {mantissa 2,base 10, exponent -1},
    field8 : {
  	       field1 -945,
	       field2 FALSE,
	       field3 NULL,
	       field4 '34AB'H,
	       field5 '1'B,
	       field6  c,
	       field7 5.2 -- {mantissa 3,base 10, exponent -1}
             }
}

mySetOfValue4 MySetOfType4 ::=
{
  {
  field1 3,
  field2 TRUE,
  field3 NULL,
  field4 '0'B,
  field5 '01'B,
  field6 a,
  field7 0,
  field8
             {
  	       field1 -9,
	       field2 FALSE,
	       field3 NULL,
	       field4 'AB'H,
	       field5 '0'B,
	       field6  c,
	       field7 5.2 -- {mantissa 3,base 2, exponent -1}
             }
  }
}
END
