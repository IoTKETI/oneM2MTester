--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Balasko, Jeno
--   Kulcsar, Endre
--   Raduly, Csaba
--
--/////////////////////////////////////////////////////////////////////////////
Test60

DEFINITIONS

AUTOMATIC TAGS

::=

BEGIN

IMPORTS ; -- nothing

MyIntegerType ::= INTEGER

myIntegerValue1 INTEGER ::= 1000

myIntegerValue2 MyIntegerType ::= -1000

myIntegerValue3 MyIntegerType ::= 0

myIntegerValue4 MyIntegerType ::= myIntegerValue1

myIntegerValue5 MyIntegerType ::= myIntegerValue2

myIntegerValue6 MyIntegerType ::= myIntegerValue3


END
