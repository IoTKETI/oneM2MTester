--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Balasko, Jeno
--   Kulcsar, Endre
--   Raduly, Csaba
--   Szabados, Kristof
--
--/////////////////////////////////////////////////////////////////////////////
Test38B  --B
DEFINITIONS

IMPLICIT TAGS


::=

BEGIN

IMPORTS ; -- nothing

zero INTEGER ::= 0
one INTEGER ::= 1
two INTEGER ::= 2
three INTEGER ::= 3
four INTEGER ::= 4
five INTEGER ::= 5
six INTEGER ::= 6
seven INTEGER ::= 7


MySequenceType1 ::= SEQUENCE {
  			     field1 [zero] INTEGER,
			     field2 [one] BOOLEAN,
			     field3 [two] NULL,
			     field4 [three] OCTET STRING OPTIONAL,
			     field5 [four] BIT STRING OPTIONAL,
			     field6 [five] ENUMERATED {a,b,c},
			     field7 [six] REAL
			    }

MySetType1 ::= SET {
  			     field1 [zero] INTEGER,
			     field2 [one] BOOLEAN,
			     field3 [two] NULL,
			     field4 [three] OCTET STRING OPTIONAL,
			     field5 [four] BIT STRING OPTIONAL,
			     field6 [five] ENUMERATED {a,b,c},
			     field7 [six] REAL,
			     field8 [seven]MySequenceType1
			    }
MyChoiceType1 ::= CHOICE
			    {
  			     field1 [zero] INTEGER,
			     field2 [one] BOOLEAN,
			     field3 [two] NULL,
			     field4 [three] OCTET STRING,
			     field5 [four] BIT STRING,
			     field6 [five] ENUMERATED {a,b,c},
			     field7 [six] REAL,
			     field8 [seven] MySequenceType1
			    }
END
