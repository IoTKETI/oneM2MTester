--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Balasko, Jeno
--   Raduly, Csaba
--
--/////////////////////////////////////////////////////////////////////////////
Asntypes DEFINITIONS /* XER INSTRUCTIONS */ AUTOMATIC TAGS
::= BEGIN

IMPORTS ; -- nothing

/*
** "Scalar" types
*/

Asn-bs ::= BIT STRING
Asn-bool ::= BOOLEAN
-- character string (see below)
-- choice
Asn-pdv ::= EMBEDDED PDV
-- enumerated
Asn-ext ::= EXTERNAL
-- instanceof
Asn-int ::= INTEGER
Asn-nul ::= NULL
-- objectclassfield
Asn-oid ::= OBJECT IDENTIFIER
Asn-odesc ::= ObjectDescriptor
Asn-os ::= OCTET STRING
Asn-real ::= REAL
Asn-roid ::= RELATIVE-OID
-- relativeOID
-- sequence
-- sequence of
-- set
-- set of
-- tagged type


-- Restricted character string types
Asn-bmp ::= BMPString
Asn-gen ::= GeneralString
Asn-gra ::= GraphicString
Asn-ia5 ::= IA5String
Asn-num ::= NumericString
Asn-prn ::= PrintableString

Asn-ttx ::= TeletexString
-- same as above: Asn-t61 ::= T61String

Asn-uni ::= UniversalString
Asn-utf ::= UTF8String
Asn-vtx ::= VideotexString

Asn-vis ::= VisibleString
-- same as above: Asn-646 ::= ISO646String

-- Unrestricted character string types
Asn-unr ::= CHARACTER STRING

------------------------------------------------------------------------

Flintstones ::= -- [USE-NUMBER] -- ENUMERATED { fred, barney, wilma, betty }
Family      ::= [58] SET OF Flintstones

------------------------------------------------------------------------

NothingToSeeHere ::= [62] SEQUENCE {}

A-rboolean ::= [64] SEQUENCE {
  bb BOOLEAN OPTIONAL
}

------------------------------------------------------------------------
Everything ::= [69] SEQUENCE {
  bitstr    BIT STRING,
  booool    BOOLEAN,
  pdv       EMBEDDED PDV,
  cartoon   Flintstones,
  outsider  EXTERNAL,
  wholenum  INTEGER,
  nix       NULL,
  emptyrec  NothingToSeeHere,
  objection OBJECT IDENTIFIER,
  octets    OCTET STRING,
  printer   PrintableString,
  floating  REAL,
  rroid     RELATIVE-OID
}

Something ::= [83] CHOICE {
  bitstr    BIT STRING,
  booool    BOOLEAN,
  pdv       EMBEDDED PDV,
  cartoon   Flintstones,
  outsider  EXTERNAL,
  wholenum  INTEGER,
  nix       NULL,
  emptyrec  NothingToSeeHere,
  objection OBJECT IDENTIFIER,
  octets    OCTET STRING,
  printer   PrintableString,
  floating  REAL,
  rroid     RELATIVE-OID
}

MaybeEverything ::= [97] SEQUENCE {
  bitstr    BIT STRING OPTIONAL,
  booool    BOOLEAN OPTIONAL,
  pdv       EMBEDDED PDV OPTIONAL,
  cartoon   Flintstones OPTIONAL,
  outsider  EXTERNAL OPTIONAL,
  wholenum  INTEGER OPTIONAL,
  nix       NULL OPTIONAL,
  anyad     ANY OPTIONAL,
  emptyrec  NothingToSeeHere OPTIONAL,
  objection OBJECT IDENTIFIER OPTIONAL,
  octets    OCTET STRING OPTIONAL,
  printer   PrintableString OPTIONAL,
  floating  REAL OPTIONAL,
  rroid     RELATIVE-OID OPTIONAL
}

Nestor ::= [111] SET OF SEQUENCE {
  name VisibleString,
  f1 SET {
    ts1 INTEGER,
    ts2 BOOLEAN
  } OPTIONAL,
  f2 Deep
}

Deep ::= [120] SEQUENCE OF SET OF SEQUENCE OF SET OF SEQUENCE {
  your CHOICE { only REAL } OPTIONAL
}

-- -- -- Built up bit by bit -- -- --

Deep1c ::= [126] CHOICE { only REAL }

Deep1s ::= [128] SEQUENCE {
  your Deep1c OPTIONAL
}

Deep2o ::= [132] SET OF Deep1s

Deep3o ::= [134] SEQUENCE OF Deep2o

Deep4o ::= [136] SET OF Deep3o

Deep5o ::= [138] SEQUENCE OF Deep4o

Nestorf1 ::= [140] SET {
    ts1 INTEGER,
    ts2 BOOLEAN
  }

NestorSeq ::= [145] SEQUENCE {
  name VisibleString DEFAULT "none",
  f1 Nestorf1 OPTIONAL,
  f2 Deep5o
}

NestorEx ::= [151] SET OF NestorSeq

------------------------------------------------------------------------

LotsaText ::= [155] SEQUENCE OF VisibleString

END
