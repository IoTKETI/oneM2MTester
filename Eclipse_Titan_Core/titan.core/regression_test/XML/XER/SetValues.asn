--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Balasko, Jeno
--   Raduly, Csaba
--
--/////////////////////////////////////////////////////////////////////////////
SetValues DEFINITIONS
AUTOMATIC TAGS ::=

BEGIN
-- EXPORTS <exports clause>;
IMPORTS 
Sobs,
Sobo,
Soc, Sonc, Sosel,
Sopdv,
Soen,
Soex,
-- Soin,
Soi,
Son,
-- Socsf,
Soid,
Soos,
Sor,
Soroid,
So-bmp,
So-gen,
So-gra,
So-ia5,
So-num,
So-prn,
So-ttx,
-- same as above: So-t61,
So-uni,
So-utf,
So-vtx,
So-vis,
-- same as above: So-646,
So-unr
FROM Sets

pdv-sx, pdv-sxs, pdv-pci, pdv-cneg, pdv-xsx,
etsi, ericsson, ber-oid, cer-oid,
nagyarvizturo, kisarvizturo, nagykisarvizturo
FROM AsnValues ;

sobs-0   Sobs ::= {}
sobo-0   Sobo ::= {}
soc-0    Soc ::= {}
sonc-0   Sonc ::= {}
sosel-0  Sosel ::= {}
sopdv-0  Sopdv ::= {}
soen-0   Soen ::= {}
soex-0   Soex ::= {}
-- soin-0 Soin ::= {}
soi-0    Soi ::= {}
son-0    Son ::= {}
-- socsf-0 Socsf ::= {}
soid-0   Soid ::= {}
soos-0   Soos ::= {}
sor-0    Sor ::= {}
soroid-0 Soroid ::= {}
so-bmp-0 So-bmp ::= {}
so-gen-0 So-gen ::= {}
so-gra-0 So-gra ::= {}
so-ia5-0 So-ia5 ::= {}
so-num-0 So-num ::= {}
so-prn-0 So-prn ::= {}
so-ttx-0 So-ttx ::= {}
-- same as above: so-t61-0 So-t61 ::= {}
so-uni-0 So-uni ::= {}
so-utf-0 So-utf ::= {}
so-vtx-0 So-vtx ::= {}
so-vis-0 So-vis ::= {}
-- same as above: so-646-0 So-646 ::= {}
so-unr-0 So-unr ::= {}

-- 1 element

sobs-1 Sobs ::= { '1110010110010011011110111010110111100111010110100110111011'B } -- A001387
sobs-2 Sobs ::= { '1110010110010011011110111010110111100111010110100110111011'B, ''B } -- A001387

sobo-1 Sobo ::= { TRUE }
soc-1 Soc ::= { is : 9.109382E-31 } -- electron mass
-- why is this not working ? sopdv-1 Sopdv ::= { {  identification syntax : { etsi 1 3 5 }, data-value 'DECAFBAD'H } }
sonc-1 Sonc ::= { is : 9.109382E-31 } -- electron mass
sosel-1 Sosel ::= {    1.602176e-19 } -- electron charge

sopdv-1 Sopdv ::= {
pdv-sx
}

soen-1 Soen ::= { fileNotFound }
soex-1 Soex ::= { {
identification	context-negotiation : {
    presentation-context-id 111,  
    transfer-syntax	ber-oid
  },
  data-value-descriptor "using context negotiation, both",
  data-value '1337D00D'H
} }
-- soin-1 Soin ::= {}
soi-1 Soi ::= { 42 }
son-1 Son ::= { NULL }
-- socsf-1 Socsf ::= {}
soid-1 Soid ::= { { 1 2 3 4 } }
soos-1 Soos ::= { '13211311123113112211'H } -- A005150
sor-1 Sor ::= { 1.602176E-19 } -- electron charge
soroid-1 Soroid ::= { { 4 3 2 1 } }
so-bmp-1 So-bmp ::= { "BMP" }
so-gen-1 So-gen ::= { "general" }
so-gra-1 So-gra ::= { "graphic" }
so-ia5-1 So-ia5 ::= { "IA5" }
so-num-1 So-num ::= { "666" }
so-prn-1 So-prn ::= { "prn" }
so-ttx-1 So-ttx ::= { "ttx" }
-- same as above: so-t61-1 So-t61 ::= {}
so-uni-1 So-uni ::= { "univ" }
so-utf-1 So-utf ::= { "utf" }
so-vtx-1 So-vtx ::= { "vtx" }
so-vis-1 So-vis ::= { "vis" }
-- same as above: so-646-1 So-646 ::= {}
so-unr-1 So-unr ::= { 
  {
    identification fixed : NULL,
    string-value 'C3815256 C38D5A54 C5B052C5 902054C3 9C4BC396 5246C39A 52C39347 C38950'H
    --            A'  R V  I'  Z T  U:  R O:   _ T U:   K O:   R F U'   R O'  G  E'  P 
    -- nagyarvizturo, UTF-8
  }  
}

-- 3

sobs-3 Sobs ::= {
  '111011'B, '11110101'B, '100110111011'B
}

sobo-3 Sobo ::= {
  TRUE, FALSE, -- FILENOTFOUND -- TRUE
}

--                       sin(1)            sin(2)            sin(3)
soc-3    Soc  ::= { is : 0.841471, is : 0.909297, is : 0.14112 }
sonc-3   Sonc ::= { is : 0.841471, is : 0.909297, is : 0.14112 }
sosel-3  Sosel ::= {     0.841471,      0.909297,      0.14112 }


sopdv-3  Sopdv ::= { pdv-xsx, pdv-pci, pdv-cneg }
soen-3   Soen ::= { truee, falsee, fileNotFound }
soex-3   Soex ::= {
  {
    identification  context-negotiation : {
      presentation-context-id 111,  
      transfer-syntax ber-oid
    },
    data-value-descriptor "using context negotiation, both",
    data-value '1337D00D'H
  },
  {
    identification  context-negotiation : {
      presentation-context-id 111,  
      transfer-syntax ber-oid
    },
    data-value-descriptor "using context negotiation, both",
    data-value '1337D00D'H
  },
  {
    identification  context-negotiation : {
      presentation-context-id 111,  
      transfer-syntax ber-oid
    },
    data-value-descriptor "using context negotiation, both",
    data-value '1337D00D'H
  }
}
-- soin-3 Soin ::= {}
soi-3    Soi ::= { 21, 1211, 111221 } -- A005150
son-3    Son ::= { NULL, NULL, NULL } -- not very interesting
-- socsf-3 Socsf ::= {}
soid-3   Soid ::= { etsi, ericsson, cer-oid }
soos-3   Soos ::= { '1123'H, '5813'H, ''H }

--                 cos(1)     cos(2)     cos(3)
sor-3    Sor ::= { 0.540302, -0.416147, -0.989992 }
soroid-3 Soroid ::= { { 1 }, { 1 1 }, { 1 1 1 } }
so-bmp-3 So-bmp ::= { "Bee", "Emm", "Pee", "" }
-- Names below are from "Command and Conquer Generals"
so-gen-3 So-gen ::= { "Alexis Alexander", "'Anvil' Shin Fai", "Rodall ""Demo"" Juhziz", "" }
so-gra-3 So-gra ::= { "3dfx", "nVidia", "Matrox", "" }
so-ia5-3 So-ia5 ::= { "IA5", "IA5", "Cthulhu fhtagn!", "" }
so-num-3 So-num ::= { "555", "436", "3747", "" }
so-prn-3 So-prn ::= { "=E1rv=EDzt=FBr=F5 t=FCk=F6rf=FAr=F3g=E9p", "=C1RV=CDZT=DBR=D5 T=DCK=D6RF=DAR=D3G=C9P", "A m=F8=F8se once bit my sister", "" }
so-ttx-3 So-ttx ::= { "Tee", "Tie", "Ecks", "" }
-- same as above: so-t61-3 So-t61 ::= {}
so-uni-3 So-uni ::= {
  "<!DOCTYPE html PUBLIC ""-//W3C//DTD XHTML 1.0 Transitional//EN"" ""http://www.w3.org/TR/xhtml1/DTD/xhtml1-transitional.dtd"">",
  "<html><head></head>",
  "<body onload='javascript.alert(""Universal"")'>&nbsp;</body></html>",
  "" }
so-utf-3 So-utf ::= { "utf", "utf", "utf", "" }
so-vtx-3 So-vtx ::= { "Vee", "Tee", "Ecxs", "" }
so-vis-3 So-vis ::= { "red", "green", "blue", "" }
-- same as above: so-646-3 So-646 ::= {}
so-unr-3 So-unr ::= {
  {
    identification fixed : NULL,
    string-value 'C3815256 C38D5A54 C5B052C5 902054C3 9C4BC396 5246C39A 52C39347 C38950'H
    --            A'  R V  I'  Z T  U:  R O:   _ T U:   K O:   R F U'   R O'  G  E'  P 
    -- nagyarvizturo, UTF-8
  },
  {
    identification syntaxes : {
      abstract { 1 2 3 4 },
      transfer { 2 7 1 8 }
    },
    string-value 'C3A17276 C3AD7A74 C5B172C5 912074C3'H -- kisarvizturo elso fele
  },
  {
    identification syntax : { 1 2 3 4 },
    string-value 'BC6BC3B6 7266C3BA 72C3B367 C3A970'H -- kisarvizturo masodik fele
  }
}

END
