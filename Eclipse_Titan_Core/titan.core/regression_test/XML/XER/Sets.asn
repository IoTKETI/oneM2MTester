--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Balasko, Jeno
--   Raduly, Csaba
--
--/////////////////////////////////////////////////////////////////////////////
Sets DEFINITIONS
  AUTOMATIC TAGS ::=

BEGIN
-- EXPORTS <exports clause>;
IMPORTS ; -- nothing

Sobs ::= [8] SET OF BIT STRING

Sobo ::= [10] SET OF BOOLEAN

Soc  ::= [12] SET OF CHOICE { is REAL }

NamedChoice ::= CHOICE { is REAL }
Sonc ::= [15] SET OF NamedChoice

-- selection type (~~ a named REAL, or "is from NamedChoice")
Sel ::= is < NamedChoice
Sosel ::= [19] SET OF Sel

Sopdv ::= [21] SET OF EMBEDDED PDV

Soen ::= [23] SET OF ENUMERATED { truee, falsee, fileNotFound }

Soex ::= [25] SET OF EXTERNAL

-- Soin ::= SET OF INSTANCE OF

Soi ::= [29] SET OF INTEGER

Son ::= [31] SET OF NULL

-- Socsf ::= SET OF object class field

Soid ::= [35] SET OF OBJECT IDENTIFIER

Soos ::= [37] SET OF OCTET STRING

Sor ::= [39] SET OF REAL

Soroid ::= [41] SET OF RELATIVE-OID

-- Restricted character string types

So-bmp ::= [45] SET OF BMPString
So-gen ::= [46] SET OF GeneralString
So-gra ::= [47] SET OF GraphicString
So-ia5 ::= [48] SET OF IA5String
So-num ::= [49] SET OF NumericString
So-prn ::= [50] SET OF PrintableString

So-ttx ::= [52] SET OF TeletexString
-- same as above: So-t61 ::= SET OF T61String

So-uni ::= [55] SET OF UniversalString
So-utf ::= [56] SET OF UTF8String
So-vtx ::= [57] SET OF VideotexString
 
So-vis ::= [59] SET OF VisibleString
-- same as above: So-646 ::= SET OF ISO646String

-- Unrestricted character string types
So-unr ::= [63] SET OF CHARACTER STRING


END
