--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Balasko, Jeno
--   Kovacs, Ferenc
--
--/////////////////////////////////////////////////////////////////////////////
TtemplateRecAsn
DEFINITIONS IMPLICIT TAGS ::= BEGIN
IMPORTS ;
-- Test for HM39698.
AmbiguousAnyRec ::= SEQUENCE
{
  argument ANY OPTIONAL
}
END
